;기준핀 홀 치수기입 리습
(DEFUN C:P3  () (COMMAND "LEADER" "_NEA" pause pause "" "%%C3 H7 DP4" ""))
(DEFUN C:P4  () (COMMAND "LEADER" "_NEA" pause pause "" "%%C4 H7 DP5" ""))
(DEFUN C:P5  () (COMMAND "LEADER" "_NEA" pause pause "" "%%C5 H7 DP6" ""))
(DEFUN C:P6  () (COMMAND "LEADER" "_NEA" pause pause "" "%%C6 H7 DP6" ""))
(DEFUN C:P8  () (COMMAND "LEADER" "_NEA" pause pause "" "%%C8 H7 DP8" ""))


(DEFUN C:P3T  () (COMMAND "LEADER" "_NEA" pause pause "" "%%C3 H7 THRU" ""))
(DEFUN C:P4T  () (COMMAND "LEADER" "_NEA" pause pause "" "%%C4 H7 THRU" ""))
(DEFUN C:P5T  () (COMMAND "LEADER" "_NEA" pause pause "" "%%C5 H7 THRU" ""))
(DEFUN C:P6T  () (COMMAND "LEADER" "_NEA" pause pause "" "%%C6 H7 THRU" ""))
(DEFUN C:P8T  () (COMMAND "LEADER" "_NEA" pause pause "" "%%C8 H7 THRU" ""))


(DEFUN C:P3B  () (COMMAND "LEADER" "_NEA" pause pause "" "%%C3 H7 DP4 배면가공" ""))
(DEFUN C:P4B  () (COMMAND "LEADER" "_NEA" pause pause "" "%%C4 H7 DP5 배면가공" ""))
(DEFUN C:P5B  () (COMMAND "LEADER" "_NEA" pause pause "" "%%C5 H7 DP6 배면가공" ""))
(DEFUN C:P6B  () (COMMAND "LEADER" "_NEA" pause pause "" "%%C6 H7 DP6 배면가공" ""))
(DEFUN C:P8B  () (COMMAND "LEADER" "_NEA" pause pause "" "%%C8.H7 DP8 배면가공" ""))
