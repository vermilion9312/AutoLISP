; 탭 치수 기입용 리습
(DEFUN C:M3 () (COMMAND "LEADER" "_NEA" pause pause "" "M3 TAP DP9" ""))
(DEFUN C:M4 () (COMMAND "LEADER" "_NEA" pause pause "" "M4 TAP DP12" ""))
(DEFUN C:M5 () (COMMAND "LEADER" "_NEA" pause pause "" "M5 TAP DP15" ""))
(DEFUN C:M6 () (COMMAND "LEADER" "_NEA" pause pause "" "M6 TAP DP18" ""))
(DEFUN C:M8 () (COMMAND "LEADER" "_NEA" pause pause "" "M8 TAP DP20" ""))
(DEFUN C:M10 () (COMMAND "LEADER" "_NEA" pause pause "" "M10 TAP DP25" ""))
(DEFUN C:M12 () (COMMAND "LEADER" "_NEA" pause pause "" "M12 TAP DP30" ""))
(DEFUN C:M14 () (COMMAND "LEADER" "_NEA" pause pause "" "M14 TAP DP35" ""))
(DEFUN C:M16 () (COMMAND "LEADER" "_NEA" pause pause "" "M16 TAP DP40" ""))
(DEFUN C:M18 () (COMMAND "LEADER" "_NEA" pause pause "" "M18 TAP DP45" ""))
(DEFUN C:M20 () (COMMAND "LEADER" "_NEA" pause pause "" "M20 TAP DP50" ""))

(DEFUN C:M3B () (COMMAND "LEADER" "_NEA" pause pause "" "M3 TAP DP9" "배면가공" ""))
(DEFUN C:M4B () (COMMAND "LEADER" "_NEA" pause pause "" "M4 TAP DP12" "배면가공" ""))
(DEFUN C:M5B () (COMMAND "LEADER" "_NEA" pause pause "" "M5 TAP DP15" "배면가공" ""))
(DEFUN C:M6B () (COMMAND "LEADER" "_NEA" pause pause "" "M6 TAP DP18" "배면가공" ""))
(DEFUN C:M8B () (COMMAND "LEADER" "_NEA" pause pause "" "M8 TAP DP20" "배면가공" ""))
(DEFUN C:M10B () (COMMAND "LEADER" "_NEA" pause pause "" "M10 TAP DP25" "배면가공" ""))
(DEFUN C:M12B () (COMMAND "LEADER" "_NEA" pause pause "" "M12 TAP DP30" "배면가공" ""))

(DEFUN C:M3T () (COMMAND "LEADER" "_NEA" pause pause "" "M3 TAP THRU" ""))
(DEFUN C:M4T () (COMMAND "LEADER" "_NEA" pause pause "" "M4 TAP THRU" ""))
(DEFUN C:M5T () (COMMAND "LEADER" "_NEA" pause pause "" "M5 TAP THRU" ""))
(DEFUN C:M6T () (COMMAND "LEADER" "_NEA" pause pause "" "M6 TAP THRU" ""))
(DEFUN C:M8T () (COMMAND "LEADER" "_NEA" pause pause "" "M8 TAP THRU" ""))
(DEFUN C:M10T () (COMMAND "LEADER" "_NEA" pause pause "" "M10 TAP THRU" ""))
(DEFUN C:M12T () (COMMAND "LEADER" "_NEA" pause pause "" "M12 TAP THRU" ""))
