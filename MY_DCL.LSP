(defun C:MY_DCL()
  (setq dcl_id (load_dialog "MY_DCL.dcl"))
  (if (not (new_dialog "MY_DCL" dcl_id))(exit))
  (action_tile "cancel" "(setq dn 1)(done_dialog)")
  (action_tile "accept" "(setq dn 2)(done_dialog)")
  (start_dialog)
  (unload_dialog dcl_id)
  (if (= dn 1)
    (princ "\n \n ...DCL_TEST Cancelled. \n")
  )
  (if (= dn 2)
    (alert "You pressed the OKAY button!")
  )
  (princ)
)
