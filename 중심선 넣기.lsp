(defun c:cc ()
    (setq olderr  *error*  *error* error)
    (setq sosmd (getvar "OSMODE"))
    (setq sblip (getvar "BLIPMODE"))
    (setq spick (getvar "PICKBOX"))
    (setvar "CMDECHO" 0)
  (setq obj_ent nil)
  (setq use_layer (getvar "clayer"))
  (setq d_s (getvar "dimscale"))
  (setq vc_org (getpoint "Pick Center.:"))
    (setvar "OSMODE" 0)
    (setvar "BLIPMODE" 0)
    (setvar "PICKBOX" 0)
  (setq xy_mode (strcase (getstring "no Xline:X no Yline:Y else Enter:")))
  (command "layer" "s" "cl" "")
  
  (cond 
   ((= xy_mode "X")
     (vcy_line)
     (setq obj_ent yl_ent)
        )
   ((= xy_mode "Y")
     (vcx_line)
    (setq obj_ent xl_ent)
      )
   ((= xy_mode "")
     (vcx_line)
     (vcy_line)
     (setq obj_ent (ssadd (ssname xl_ent 0)))
     (setq obj_ent (ssadd (ssname yl_ent 0) obj_ent))
        )
      ) ;cond
  
  (command "scale" obj_ent "" vc_org pause)
  
  (command "layer" "s" use_layer "")
    (setvar "PICKBOX" spick)
    (setvar "OSMODE" sosmd)
    (setvar "BLIPMODE" sblip)
    (setvar "CMDECHO" 1)
    (prin1)
    
  
  )
