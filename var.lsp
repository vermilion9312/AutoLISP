(defun c:qq (/ num01 num02)
  (define_variables)
  (print_variables)
  (princ)
)

(defun define_variables ()
  (setq num01 20)
  (setq num02 "world")
)

(defun print_variables ()
  (princ num01)
  (princ num02)
)

(defun *ERROR* (message)
  (princ "\nError: ")
  (princ message)
)
